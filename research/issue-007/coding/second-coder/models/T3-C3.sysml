package InfusionPumpAlarmSystem {
    private import ScalarValues::*;
    private import SI::*;

    part def FluidLine {
        attribute isOccluded : Boolean = false;
        port inlet;
        port outlet;
    }

    part def PressureSensor {
        attribute measuredPressure : Real;
        attribute occlusionThreshold : Real;
        port sense;
    }

    part def AlarmDevice {
        attribute audible : Boolean = false;
        attribute visible : Boolean = false;
    }

    part def PumpDrive {
        attribute delivering : Boolean = false;
        attribute flowRate : Real;
    }

    part def InfusionPump {
        attribute configuredThreshold : Real;
        part line : FluidLine;
        part sensor : PressureSensor;
        part alarm : AlarmDevice;
        part drive : PumpDrive;
    }

    part pump : InfusionPump;

    requirement def OcclusionAlarmRequirement {
        subject p : InfusionPump;
        doc /* The pump shall raise an audible and visible alarm within 2 seconds of an occlusion
               being detected, and shall stop delivery at the same time. */
        attribute maxAlarmDelay : Real = 2.0;
    }

    requirement occlusionAlarm : OcclusionAlarmRequirement;
    satisfy occlusionAlarm by pump;

    connection sensorSignal connect pump.sensor.sense to pump.drive;
    connection lineFlow connect pump.drive to pump.line.inlet;
}
