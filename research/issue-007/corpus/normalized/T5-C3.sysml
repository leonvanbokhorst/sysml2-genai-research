package GroundStationSchedulingSystem {
    private import ScalarValues::*;

    part def VisibilityWindow {
        attribute startTime : Real;
        attribute endTime : Real;
    }

    part def Satellite {
        attribute satelliteId : String;
        attribute window : VisibilityWindow;
    }

    part def Antenna {
        attribute isPointed : Boolean = false;
        attribute azimuth : Real;
        attribute elevation : Real;
    }

    part def Transceiver {
        attribute isActive : Boolean = false;
        attribute band : String = "S";
    }

    part def GroundStation {
        part antenna : Antenna;
        part transceiver : Transceiver;
        part satellites : Satellite[1..*];
    }

    part station : GroundStation;

    requirement def ContactInsideWindowRequirement {
        subject s : GroundStation;
        doc /* A contact may only be scheduled inside a satellite's visibility window, and the
               antenna shall be pointed before the window opens. Only one contact at a time. */
    }

    requirement contactInsideWindow : ContactInsideWindowRequirement;
    satisfy contactInsideWindow by station;

    action def ScheduleContact {
        in sat : Satellite;
        action checkWindow {
            out allowed : Boolean;
        }
        action pointAntenna {
            out pointed : Boolean;
        }
        action openLink {
            out linked : Boolean;
        }
        first checkWindow;
        then pointAntenna;
        then openLink;
    }

    connection antennaToTransceiver connect station.antenna to station.transceiver;
}
