package LevelCrossingProtection {
    private import ScalarValues::*;

    part def BarrierArm {
        attribute lowered : Boolean = false;
    }

    part def BarrierMotor {
        attribute running : Boolean = false;
    }

    part def RedLight {
        attribute flashing : Boolean = false;
    }

    part def TrainDetector {
        attribute state : String;
    }

    part def Crossing {
        part motor : BarrierMotor;
        part arms : BarrierArm[2];
        part lights : RedLight[2];
        part detector : TrainDetector;
    }

    requirement def LowerBeforeArrival {
        doc /* The barrier shall be fully lowered before the train reaches the crossing. */
        subject crossing : Crossing;
    }

    requirement lowerBeforeArrival : LowerBeforeArrival;
    satisfy lowerBeforeArrival;

    state def CrossingStates {
        state idle;
        state lowering;
        state down;
        state raising;
        transition idle then lowering;
        transition lowering then down;
        transition down then raising;
        transition raising then idle;
    }

    part levelCrossing : Crossing;
}
