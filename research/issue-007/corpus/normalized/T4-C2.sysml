package WarehouseAgvFleet {
    private import ScalarValues::*;

    part def Battery {
        attribute stateOfCharge : Real;
        attribute charging : Boolean = false;
    }

    part def DockingStation {
        attribute occupied : Boolean = false;
    }

    part def Agv {
        part battery : Battery;
        attribute hasJob : Boolean = false;
        attribute charging : Boolean = false;
    }

    part def FleetController {
        part agvs : Agv[10];
        part docks : DockingStation[4];
    }

    requirement def ReturnToDockBelowFifteen {
        subject fleet : FleetController;
        doc /* Each AGV shall dock when its state of charge falls below 15% and shall not accept a
               new job while charging. */
        attribute threshold : Real = 15.0;
    }

    requirement returnToDock : ReturnToDockBelowFifteen;
    satisfy returnToDock by fleet;

    action def AssignTransportJob {
        in job : String;
        in agv : Agv;
        out accepted : Boolean;
        action checkCharge;
        action checkAvailability;
        action dispatch;
        first checkCharge;
        then checkAvailability;
        then dispatch;
    }
}
