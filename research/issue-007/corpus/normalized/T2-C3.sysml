package LevelCrossingSystem {
    private import ScalarValues::*;

    port def CommandPort;

    part def BarrierArm {
        attribute position : Real = 0.0;
        attribute isLowered : Boolean = false;
    }

    part def BarrierMotor {
        attribute isRunning : Boolean = false;
        attribute torque : Real;
        port command : CommandPort;
    }

    part def WarningLight {
        attribute isFlashing : Boolean = false;
    }

    part def TrainDetector {
        attribute reportedState : String;
        port track;
    }

    part def CrossingController {
        part motor : BarrierMotor;
        part detector : TrainDetector;
        port command : CommandPort;
    }

    part def LevelCrossing {
        part controller : CrossingController;
        part leftArm : BarrierArm;
        part rightArm : BarrierArm;
        part lights : WarningLight[2];
    }

    part crossing : LevelCrossing;

    requirement def LowerBeforeArrivalRequirement {
        subject c : LevelCrossing;
        doc /* The barrier shall be fully lowered before the train reaches the crossing, and shall
               rise only after the train has cleared it. */
    }

    requirement lowerBeforeArrival : LowerBeforeArrivalRequirement;
    satisfy lowerBeforeArrival by crossing;

    state def CrossingStates {
        state idle;
        state lowering {
            entry action lowerArms;
        }
        state closed;
        state raising;

        transition idle then lowering;
        transition lowering then closed;
        transition closed then raising;
        transition raising then idle;
    }

    action def lowerArms {
        out done : Boolean;
    }

    connection controllerToMotor connect crossing.controller.command to crossing.controller.motor.command;
}
