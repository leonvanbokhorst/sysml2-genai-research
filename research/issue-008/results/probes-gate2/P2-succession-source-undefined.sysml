// Gate-2 probe (O5): dangling succession SOURCE, the site A's corpus exercises. Not a frozen mutant.
package P2SuccessionSource {
    private import ScalarValues::*;

    action def Cycle {
        action sense;
        first start;
        then sense;
    }
}
