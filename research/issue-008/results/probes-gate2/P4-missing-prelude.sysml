// Gate-2 probe (O6): the documented stdlib-prelude confound. No import. Not a frozen mutant.
package P4MissingPrelude {
    part def Tank {
        attribute volume : Real;
        attribute isFull : Boolean = false;
    }
}
