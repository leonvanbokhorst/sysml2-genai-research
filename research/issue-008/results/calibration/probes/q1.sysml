package Q1 {
    private import ScalarValues::*;
    private import ISQ::*;
    private import SI::*;
    attribute m : MassValue = 1200.0 [kg];
    attribute d : LengthValue = 4.5 [m];
    attribute v : SpeedValue = 1200.0 [kg];
}
